class Propulsion {
    mass : ScalarValues::Integer = 5;

}

class Power {
    mass : ScalarValues::Integer;

}

class Avionics {
    mass : ScalarValues::Integer;

}

class Thermal {
    mass : ScalarValues::Integer;

}

class Structure {
    mass : ScalarValues::Integer;

}
